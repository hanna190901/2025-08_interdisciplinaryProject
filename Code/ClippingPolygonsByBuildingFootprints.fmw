FME workspace ClippingPolygonsByBuildingFootprints.fmw

Parameters:
- SourceDataset_SHAPEFILE = F:\KRE\SolaranlagenBerlin\results\AllBerlinSolarSystems_25833_clean.shp\Shapefile1.shp   # Source Esri Shapefile(s)
- SourceDataset_SHAPEFILE_3 = C:\Users\hkretz\OneDrive - virtualcitysystems GmbH\2 interdisziplinäresProjekt\6 Auswertung\Gebäudeverschnitt\gebäudeBerlin.shp   # Source Esri Shapefile(s)
- DestDataset_SHAPEFILE = F:\KRE\SolaranlagenBerlin\results\AllBerlinSolarSystems_25833_clean_clippedBuilding2.shp   # Destination Esri Shapefile Folder

Readers:
- SHAPEFILE_1: SHAPEFILE from $(SourceDataset_SHAPEFILE)
- SHAPEFILE_2: SHAPEFILE from $(SourceDataset_SHAPEFILE_3)

Writers:
- SHAPEFILE_3: SHAPEFILE to $(DestDataset_SHAPEFILE) in EPSG:25833

gebäudeBerlin (reader SHAPEFILE_2)
    attributes: uuid varchar(254), gfk long, bezgfk varchar(254), ofl long, bezofl varchar(254), aog long, aug long, hoh varchar(254), bat long, bezbat varchar(254), nam varchar(254), baw long, bezbaw varchar(254), zus long, bezzus varchar(254), gkn varchar(254), des varchar(254), bezdes varchar(254), lag varchar(254), namlag varchar(254), hnr varchar(254), pnr varchar(254), lnr varchar(254), bezeich varchar(254)
    -> Reprojector
Reprojector
    DEST = EPSG:25833
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Clipper [CLIPPER]
    REPROJECTED -> PointOnAreaOverlayer [AREA]
Shapefile1 (reader SHAPEFILE_1)
    attributes: Shapefi_ID varchar(5)
    -> UniqueIdentifierGenerator
UniqueIdentifierGenerator
    UUID_ATTR = _uuid
    UUID_FORMAT = UUID_ONLY
    -> CenterPointReplacer
    -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> FeatureMerger [REQUESTOR]
CenterPointReplacer
    POINTTYPE = CENTEROFGRAV
    POINT -> PointOnAreaOverlayer [POINT]
PointOnAreaOverlayer
    ATTR_ACCUM_MODE = Merge Incoming
    ATTR_CONFLICT_RES_LOOKUP = ORIGINAL_IF_CONFLICT
    DEAGGREGATE_INPUT = Yes
    OV_ATTR = _overlaps
    POLYS_FIRST = NO
    ATTR_CONFLICT_RES = Use Original
    POINT -> AttributeManager
AttributeManager
    ATTR_TABLE:
      RENAME_SET_VALUE bezgfk > Nutzung (varchar(254))
      RENAME_SET_VALUE lag > PLZ (varchar(254))
      RENAME_SET_VALUE namlag > Adresse (varchar(254))
      REMOVE uuid (varchar(254))
      REMOVE gfk (int32)
      REMOVE ofl (int32)
      REMOVE bezofl (varchar(254))
      REMOVE aog (int32)
      REMOVE aug (int32)
      REMOVE hoh (varchar(254))
      REMOVE bat (int32)
      REMOVE bezbat (varchar(254))
      REMOVE nam (varchar(254))
      REMOVE baw (int32)
      REMOVE bezbaw (varchar(254))
      REMOVE zus (int32)
      REMOVE bezzus (varchar(254))
      REMOVE gkn (varchar(254))
      REMOVE des (varchar(254))
      REMOVE bezdes (varchar(254))
      REMOVE hnr (varchar(254))
      REMOVE pnr (varchar(254))
      REMOVE lnr (varchar(254))
      REMOVE bezeich (varchar(254))
      REMOVE _overlaps (uint32)
    -> FeatureMerger [SUPPLIER]
FeatureMerger
    ATTR_ACCUM_MODE = Merge Supplier
    ATTR_CONFLICT_RES_LOOKUP = REQUESTOR_IF_CONFLICT
    IGNORE_NULLS = No
    JOIN_KEYS = @Value(_uuid) @Value(_uuid) AUTO
    MERGE_TYPE = Attributes Only
    PROCESS_DUPS = NO
    REJECT_NULL_MISSING_KEYS = No
    SUPPLIERS_FIRST = No
    ATTR_CONFLICT_RES = Use Requestor
    MERGED -> clippedBuilding2 (writer SHAPEFILE_3)
clippedBuilding2 (writer SHAPEFILE_3)
    attributes: Shapefi_ID varchar(5), Q__uuid varchar(36), Q__clipped varchar(3), Nutzung varchar(254), PLZ varchar(254), Adresse varchar(254)
