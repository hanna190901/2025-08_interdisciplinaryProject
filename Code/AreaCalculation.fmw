FME workspace AreaCalculation.fmw

Parameters:
- SourceDataset_GEOJSON = F:\KRE\SolaranlagenBerlin\results\AllBerlinSolarSystems.geojson   # Source GeoJSON File or URL
- DestDataset_GEOJSON = F:\KRE\SolaranlagenBerlin\results\AllBerlinSolarSystems_area.geojson   # Destination GeoJSON File

Readers:
- GEOJSON_1: GEOJSON from $(SourceDataset_GEOJSON) in EPSG:25833

Writers:
- GEOJSON_2: GEOJSON to $(DestDataset_GEOJSON) in EPSG:25833

AllBerlinSolarSystems (reader GEOJSON_1)
    attributes: _clipped string, _label string, id int
    -> AreaCalculator
AreaCalculator
    AREA_ATTR = _area
    AREA_TYPE = Plane Area
    MULT = 1
    -> Writer (writer GEOJSON_2)
Writer (writer GEOJSON_2)
    attributes: _clipped string, _label string, id int, _area float
