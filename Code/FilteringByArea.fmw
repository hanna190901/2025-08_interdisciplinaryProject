FME workspace FilteringByArea.fmw

Parameters:
- DestDataset_SHAPEFILE_2 = F:\KRE\SolaranlagenBerlin\results\5 Analyse_cleaned_clippedBuildings\BerlinSolarSystems_25833_clean_clippedBuilding2_area_o1.shp   # Destination Esri Shapefile Folder
- DestDataset_SHAPEFILE = F:\KRE\SolaranlagenBerlin\results\5 Analyse_cleaned_clippedBuildings\BerlinSolarSystems_25833_clean_clippedBuilding2_area_u1.shp   # Destination Esri Shapefile Folder
- SourceDataset_SHAPEFILE = F:\KRE\SolaranlagenBerlin\results\AllBerlinSolarSystems_25833_clean_clippedBuilding2.shp\clippedBuilding2.shp   # Source Esri Shapefile(s)

Readers:
- SHAPEFILE_2: SHAPEFILE from $(SourceDataset_SHAPEFILE)

Writers:
- SHAPEFILE_1: SHAPEFILE to $(DestDataset_SHAPEFILE) in EPSG:25833
- SHAPEFILE_3: SHAPEFILE to $(DestDataset_SHAPEFILE_2) in EPSG:25833

clippedBuilding2 (reader SHAPEFILE_2)
    attributes: Shapefi_ID varchar(5), Q__uuid varchar(36), Q__clipped varchar(3), Nutzung varchar(254), PLZ varchar(254), Adresse varchar(254)
    -> AreaCalculator
AreaCalculator
    AREA_ATTR = _area
    AREA_TYPE = Plane Area
    MULT = 1
    -> kleiner_1
    -> größer_1
kleiner_1: Tester
    BOOL_OP = OR
    TEST_CLAUSE = TEST @Value(_area) < 1
    TEST_MODE = TEST
    PASSED -> Sorter_2
Sorter_2
    SORT_PARM = _area NATURAL ASCENDING
    SORTED -> u1 (writer SHAPEFILE_1)
u1 (writer SHAPEFILE_1)
    attributes: Q__uuid varchar(36), Q__clipped varchar(3), Nutzung varchar(254), PLZ varchar(254), Adresse varchar(254), Q__area double
größer_1: Tester
    BOOL_OP = OR
    TEST_CLAUSE = TEST @Value(_area) >= 1
    TEST_MODE = TEST
    PASSED -> Sorter
Sorter
    SORT_PARM = _area NATURAL DESCENDING
    SORTED -> o1 (writer SHAPEFILE_3)
o1 (writer SHAPEFILE_3)
    attributes: Q__uuid varchar(36), Q__clipped varchar(3), Nutzung varchar(254), PLZ varchar(254), Adresse varchar(254), Q__area double
