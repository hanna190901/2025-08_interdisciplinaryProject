FME workspace ComparisonWithMaStR.fmw

Parameters:
- SourceDataset_CSV2 = ""C:\Users\hkretz\OneDrive - virtualcitysystems GmbH\2 interdisziplinäresProjekt\5 Marktstammdatenregister\StromerzeugerSolar_1_bis_25000.csv" "C:\Users\hkretz\OneDrive - virtualcitysystems GmbH\2 interdisziplinäresProjekt\5 Marktstammdatenregister\StromerzeugerSolar_25001_bis_49127.csv""   # Source CSV (Comma Separated Value) File(s)
- FEATURE_TYPES =
- SourceDataset_SHAPEFILE = F:\KRE\SolaranlagenBerlin\results\AllBerlinSolarSystems_25833_clean_clippedBuilding2.shp\clippedBuilding2.shp   # Source Esri Shapefile(s)
- FEATURE_TYPES_2 =
- SourceDataset_SHAPEFILE_5 = C:\Users\hkretz\OneDrive - virtualcitysystems GmbH\2 interdisziplinäresProjekt\6 Auswertung\Gebäudeverschnitt\gebäudeBerlin.shp\gebäudeBerlin.shp   # Source Esri Shapefile(s)
- DestDataset_CSV2 = C:\Users\hkretz\OneDrive - virtualcitysystems GmbH\2 interdisziplinäresProjekt\6 Auswertung\Vgl_Marktstammdatenregister   # Destination CSV (Comma Separated Value) Folder
- SourceDataset_SHAPEFILE_4 = C:\Users\hkretz\OneDrive - virtualcitysystems GmbH\2 interdisziplinäresProjekt\6 Auswertung\Vgl_Marktstammdatenregister\plz.shp\plz.shp   # Source Esri Shapefile(s)

Readers:
- CSV2_1: CSV2 from $(SourceDataset_CSV2)
- SHAPEFILE_1: SHAPEFILE from $(SourceDataset_SHAPEFILE)
- SHAPEFILE_2: SHAPEFILE from $(SourceDataset_SHAPEFILE_5)
- SHAPEFILE_3: SHAPEFILE from $(SourceDataset_SHAPEFILE_4)

Writers:
- CSV2_2: CSV2 to $(DestDataset_CSV2)

CSV (reader CSV2_1)
    attributes: MaStR-Nr. der Einheit varchar(15), Anzeige-Name der Einheit varchar(255), Betriebs-Status varchar(10), Energieträger varchar(24), Bruttoleistung der Einheit varchar(255), Nettonennleistung der Einheit real32, Inbetriebnahmedatum der Einheit varchar(10), Registrierungsdatum der Einheit varchar(10), Bundesland varchar(6), Postleitzahl uint32, Ort varchar(6), Straße varchar(255), Hausnummer varchar(255), Gemarkung varchar(255), Flurstück varchar(255), Gemeindeschlüssel uint32, Gemeinde varchar(6), Landkreis varchar(6), Koordinate: Breitengrad (WGS84) y_coordinate, Koordinate: Längengrad (WGS84) x_coordinate, Technologie der Stromerzeugung varchar(1), Art der Solaranlage varchar(49), Anzahl der Solar-Module uint32, Hauptausrichtung der Solar-Module varchar(12), Art der Bodenfläche (der PV-Anlage) varchar(255), Name des Windparks varchar(1), Wind an Land oder auf See varchar(1), Nabenhöhe der Windenergieanlage varchar(1), Rotordurchmesser der Windenergieanlage varchar(1), Hersteller der Windenergieanlage varchar(1),
      Typenbezeichnung varchar(1), Hauptbrennstoff der Einheit varchar(1), MaStR-Nr. der Speichereinheit varchar(1), Speichertechnologie varchar(1), Nutzbare Speicherkapazität in kWh varchar(1), Letzte Aktualisierung varchar(10), Datum der endgültigen Stilllegung varchar(1), Datum der geplanten Inbetriebnahme varchar(1), Name des Anlagenbetreibers (nur Org.) varchar(101), MaStR-Nr. des Anlagenbetreibers varchar(15), Volleinspeisung oder Teileinspeisung varchar(48), MaStR-Nr. der Genehmigung varchar(255), Name des Anschluss-Netzbetreibers varchar(255), MaStR-Nr. des Anschluss-Netzbetreibers varchar(32), Netzbetreiberprüfung varchar(16), Spannungsebene varchar(255), MaStR-Nr. der Lokation varchar(15), MaStR-Nr. der EEG-Anlage varchar(15), EEG-Anlagenschlüssel varchar(33), Inbetriebnahmedatum der EEG-Anlage varchar(10), Installierte Leistung der EEG-Anlage varchar(255), Zuschlagnummer (EEG/KWK-Ausschreibung) varchar(255), MaStR-Nr. der KWK-Anlage varchar(1), Inbetriebnahmedatum der KWK-Anlage varchar(1), Elektrische KWK-Leistung varchar(1), Thermische Nutzleistung in kW varchar(1)
    -> StatisticsCalculator
StatisticsCalculator
    ATTR_ACCUM_MODE = None
    CALCULATION_MODE = NUMERIC
    FEAT_STATS = MaStR-Nr. der EEG-Anlage,NUMERIC_MODE,,,COUNT,,,,,,,,,,
    GROUP_BY = Postleitzahl
    SUMMARY -> FeatureJoiner [LEFT]
plz (reader SHAPEFILE_3)
    attributes: plz varchar(254)
    -> SpatialFilter_2 [Filter]
gebäudeBerlin (reader SHAPEFILE_2)
    attributes: uuid varchar(254), gfk long, bezgfk varchar(254), ofl long, bezofl varchar(254), aog long, aug long, hoh varchar(254), bat long, bezbat varchar(254), nam varchar(254), baw long, bezbaw varchar(254), zus long, bezzus varchar(254), gkn varchar(254), des varchar(254), bezdes varchar(254), lag varchar(254), namlag varchar(254), hnr varchar(254), pnr varchar(254), lnr varchar(254), bezeich varchar(254)
    -> SpatialFilter [Filter]
clippedBuilding2 (reader SHAPEFILE_1)
    attributes: Q__uuid varchar(36), Q__clipped varchar(3), Nutzung varchar(254), PLZ varchar(254), Adresse varchar(254)
    -> SpatialFilter [Candidate]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator_2
StatisticsCalculator_2
    ATTR_ACCUM_MODE = None
    CALCULATION_MODE = NUMERIC
    FEAT_STATS = uuid,NUMERIC_MODE,,,COUNT,,,,,,,,,,
    GROUP_BY = uuid
    COMPLETE -> DuplicateFilter
DuplicateFilter
    INPUT_ORDERED_CHOICE_LOOKUP = NO
    KEYATTR = uuid
    INPUT_ORDERED_CHOICE = No
    UNIQUE -> SpatialFilter_2 [Candidate]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> StatisticsCalculator_3
StatisticsCalculator_3
    ATTR_ACCUM_MODE = None
    CALCULATION_MODE = NUMERIC
    FEAT_STATS = uuid,NUMERIC_MODE,,,COUNT,,,,,,,,,,
    GROUP_BY = plz
    SUMMARY -> FeatureJoiner [RIGHT]
FeatureJoiner
    ATTR_CONFLICT_RES_LOOKUP = USE_LEFT
    GEOMETRY_HANDLING_LOOKUP = USE_LEFT
    JOIN_KEYS = Postleitzahl plz AUTO
    JOIN_MODE = Inner
    ATTR_CONFLICT_RES = Prefer Left
    GEOMETRY_HANDLING = Prefer Left
    JOINED -> AttributeCreator
AttributeCreator
    ATTR_TABLE = SET_TO dif (varchar(200)) =  @sub(@Value(uuid.total_count),@Value(MaStR-Nr. der EEG-Anlage.total_count))
    -> GeoAI-MSDR (writer CSV2_2)
GeoAI-MSDR (writer CSV2_2)
    attributes: dif varchar(200), Postleitzahl uint32, MaStR-Nr. der EEG-Anlage.total_count uint64, plz varchar(254), uuid.total_count uint64
