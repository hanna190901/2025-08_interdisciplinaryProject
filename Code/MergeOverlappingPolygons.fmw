FME workspace MergeOverlappingPolygons.fmw

Parameters:
- DestDataset_SHAPEFILE = F:\KRE\SolaranlagenBerlin\results\AllBerlinSolarSystems_25833_clean.shp   # Destination Esri Shapefile Folder
- SourceDataset_SHAPEFILE = F:\KRE\SolaranlagenBerlin\results\AllBerlinSolarSystems_area_25833.shp\Shapefile1.shp   # Source Esri Shapefile(s)

Readers:
- SHAPEFILE_2: SHAPEFILE from $(SourceDataset_SHAPEFILE)

Writers:
- SHAPEFILE_1: SHAPEFILE to $(DestDataset_SHAPEFILE) in EPSG:25833

Shapefile1 (reader SHAPEFILE_2)
    attributes: Q__clipped varchar(3), Q__label varchar(254), Q__area number(31,15)
    -> Dissolver
Dissolver
    ACCUM_INPUT_ATTRS = Drop Incoming Attributes
    CLEANING_TOLERANCE_LOOKUP = AUTO
    CONNECT_Z_MODE_LOOKUP = FIRST_WINS
    DEAGGREGATE_INPUT = Yes
    CLEANING_TOLERANCE = Automatic
    CONNECT_Z_MODE = First Wins
    AREA -> Shapefile1 (writer SHAPEFILE_1)
Shapefile1 (writer SHAPEFILE_1)
