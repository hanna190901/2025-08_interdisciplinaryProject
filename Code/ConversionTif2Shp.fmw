FME workspace ConversionTif2Shp.fmw

Parameters:
- SourceDataset_GEOJSON = C:\Users\hkretz\OneDrive - virtualcitysystems GmbH\2 interdisziplinäresProjekt\2 Datenvorbereitung\Shapes\OSMB-Berlin.geojson   # Source GeoJSON File or URL
- FEATURE_TYPES_2 =
- SourceDataset_GEOTIFF = F:\KRE\SolaranlagenBerlin\results\batch2\*.tif   # Source GeoTIFF File(s) or URL(s)
- FEATURE_TYPES =
- SourceDataset_GEOTIFF_9 = F:\KRE\SolaranlagenBerlin\results\batch3\*.tif   # Source GeoTIFF File(s) or URL(s)
- FEATURE_TYPES_3 =
- SourceDataset_GEOTIFF_13 = F:\KRE\SolaranlagenBerlin\results\batch4\*.tif   # Source GeoTIFF File(s) or URL(s)
- FEATURE_TYPES_4 =
- SourceDataset_GEOTIFF_11 = F:\KRE\SolaranlagenBerlin\results\batch5\*.tif   # Source GeoTIFF File(s) or URL(s)
- FEATURE_TYPES_5 =
- SourceDataset_GEOTIFF_8 = F:\KRE\SolaranlagenBerlin\results\batch6\*.tif   # Source GeoTIFF File(s) or URL(s)
- FEATURE_TYPES_6 =
- SourceDataset_GEOTIFF_10 = F:\KRE\SolaranlagenBerlin\results\batch7\*.tif   # Source GeoTIFF File(s) or URL(s)
- FEATURE_TYPES_7 =
- SourceDataset_GEOTIFF_12 = F:\KRE\SolaranlagenBerlin\results\batch1\*.tif   # Source GeoTIFF File(s) or URL(s)
- FEATURE_TYPES_8 =
- DestDataset_SHAPEFILE_9 = F:\KRE\SolaranlagenBerlin\results\alleGeojsonsBatchs2\batch2.shp   # Destination Esri Shapefile Folder
- DestDataset_SHAPEFILE_13 = F:\KRE\SolaranlagenBerlin\results\alleGeojsonsBatchs2\batch3.shp   # Destination Esri Shapefile Folder
- DestDataset_SHAPEFILE_11 = F:\KRE\SolaranlagenBerlin\results\alleGeojsonsBatchs2\batch4.shp   # Destination Esri Shapefile Folder
- DestDataset_SHAPEFILE_8 = F:\KRE\SolaranlagenBerlin\results\alleGeojsonsBatchs2\batch5.shp   # Destination Esri Shapefile Folder
- DestDataset_SHAPEFILE_10 = F:\KRE\SolaranlagenBerlin\results\alleGeojsonsBatchs2\batch6.shp   # Destination Esri Shapefile Folder
- DestDataset_SHAPEFILE_12 = F:\KRE\SolaranlagenBerlin\results\alleGeojsonsBatchs2\batch7.shp   # Destination Esri Shapefile Folder
- DestDataset_SHAPEFILE = F:\KRE\SolaranlagenBerlin\results\alleGeojsonsBatchs2\batch1.shp   # Destination Esri Shapefile Folder

Readers:
- GEOJSON_1: GEOJSON from $(SourceDataset_GEOJSON)
- GEOTIFF_1: GEOTIFF from $(SourceDataset_GEOTIFF) in EPSG:25833
- GEOTIFF_2: GEOTIFF from $(SourceDataset_GEOTIFF_9) in EPSG:25833
- GEOTIFF_3: GEOTIFF from $(SourceDataset_GEOTIFF_13) in EPSG:25833
- GEOTIFF_4: GEOTIFF from $(SourceDataset_GEOTIFF_11) in EPSG:25833
- GEOTIFF_5: GEOTIFF from $(SourceDataset_GEOTIFF_8) in EPSG:25833
- GEOTIFF_6: GEOTIFF from $(SourceDataset_GEOTIFF_10) in EPSG:25833
- GEOTIFF_7: GEOTIFF from $(SourceDataset_GEOTIFF_12) in EPSG:25833

Writers:
- SHAPEFILE_1: SHAPEFILE to $(DestDataset_SHAPEFILE) in EPSG:25833
- SHAPEFILE_2: SHAPEFILE to $(DestDataset_SHAPEFILE_9) in EPSG:25833
- SHAPEFILE_3: SHAPEFILE to $(DestDataset_SHAPEFILE_13) in EPSG:25833
- SHAPEFILE_4: SHAPEFILE to $(DestDataset_SHAPEFILE_11) in EPSG:25833
- SHAPEFILE_5: SHAPEFILE to $(DestDataset_SHAPEFILE_8) in EPSG:25833
- SHAPEFILE_6: SHAPEFILE to $(DestDataset_SHAPEFILE_10) in EPSG:25833
- SHAPEFILE_7: SHAPEFILE to $(DestDataset_SHAPEFILE_12) in EPSG:25833

OSMB-Berlin (reader GEOJSON_1)
    attributes: osm_id int, name string, name_en string, boundary string, admin_level int, admin_centre_node_id int, admin_centre_node_lat float, admin_centre_node_lng float, label_node_id string, label_node_lat string, label_node_lng string
    -> GeometryValidator
GeometryValidator
    ISSUE_ATTR_NAME = _issues
    PRESETS = Custom
    REPAIR = Yes
    RULES = SHELL_VALIDATION FLIP_APPEARANCE_MODE]FLIP_APPEARANCES]FME_CONTROLLER_QUERY_FILE]transformers/dependencies/geometryvalidator8/SHELL_VALIDATION.fme]FME_CONTROLLER_CHOICE]SHELL_VALIDATION SELF_INTERSECTING CHECK_HOLE_TOUCHING_POLYGON]No]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING NULL_REMOVAL FME_CONTROLLER_QUERY_FILE]transformers/dependencies/geometryvalidator8/NULL_REMOVAL.fme]FME_CONTROLLER_CHOICE]NULL_REMOVAL CONSECUTIVE_IDENTICAL_VERTICES_2D CHECK_Z]YES]TOLERANCE]0.0]FME_CONTROLLER_QUERY_FILE]transformers/dependencies/geometryvalidator8/CONSECUTIVE_IDENTICAL_VERTICES_2D.fme]FME_CONTROLLER_CHOICE]CONSECUTIVE_IDENTICAL_VERTICES_2D NAN_REMOVAL PROCESS_MEASURE]NO]FME_CONTROLLER_QUERY_FILE]transformers/dependencies/geometryvalidator8/NAN_REMOVAL.fme]FME_CONTROLLER_CHOICE]NAN_REMOVAL MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS
    SUMMARY = Detailed
    PASSED -> Reprojector
Reprojector
    DEST = EPSG:25833
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Clipper [CLIPPER]
    REPROJECTED -> Clipper_2 [CLIPPER]
    REPROJECTED -> Clipper_3 [CLIPPER]
    REPROJECTED -> Clipper_6 [CLIPPER]
    REPROJECTED -> Clipper_4 [CLIPPER]
    REPROJECTED -> Clipper_5 [CLIPPER]
    REPROJECTED -> Clipper_7 [CLIPPER]
GEOTIFF (reader GEOTIFF_7)
    -> Clipper_7 [CANDIDATE]
Clipper_7
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterMosaicker_7
RasterMosaicker_7
    ACCUM_ATTRS_NAME = Use Attributes From One Feature
    INTERPOLATION_TYPE = NearestNeighbor
    MERGE_PALETTES_NAME = Yes
    NODATA_OVERWRITE = No
    OVERLAPPING_VALUES = last
    SNAPPING_TYPE = RESAMPLE
    INTERPOLATION_TYPE_NAME = Nearest Neighbor
    MERGE_PALETTES = Yes
    SNAPPING_TYPE_NAME = Resample
    -> RasterToPolygonCoercer_7
RasterToPolygonCoercer_7
    EXTRACT_NODATA = No
    LABEL_ATTRIBUTE = _label
    PRESERVE_ATTRIBUTES_LOOKUP = YES
    EXTRACT_NODATA_LOOKUP = No
    PRESERVE_ATTRIBUTES = Yes
    POLYGONS -> Shapefile1 (writer SHAPEFILE_1)
Shapefile1 (writer SHAPEFILE_1)
    attributes: Q__clipped varchar(3), Q__label varchar(254)
GEOTIFF (reader GEOTIFF_1)
    -> Reprojector_2
    -> Clipper [CANDIDATE]
Reprojector_2 [off]
    DEST = EPSG:25833
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Clipper [CANDIDATE]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterMosaicker
RasterMosaicker
    ACCUM_ATTRS_NAME = Use Attributes From One Feature
    INTERPOLATION_TYPE = NearestNeighbor
    MERGE_PALETTES_NAME = Yes
    NODATA_OVERWRITE = No
    OVERLAPPING_VALUES = last
    SNAPPING_TYPE = RESAMPLE
    INTERPOLATION_TYPE_NAME = Nearest Neighbor
    MERGE_PALETTES = Yes
    SNAPPING_TYPE_NAME = Resample
    -> RasterToPolygonCoercer
RasterToPolygonCoercer
    EXTRACT_NODATA = No
    LABEL_ATTRIBUTE = _label
    PRESERVE_ATTRIBUTES_LOOKUP = YES
    EXTRACT_NODATA_LOOKUP = No
    PRESERVE_ATTRIBUTES = Yes
    POLYGONS -> Shapefile2 (writer SHAPEFILE_2)
Shapefile2 (writer SHAPEFILE_2)
    attributes: Q__clipped varchar(3), Q__label varchar(254)
GEOTIFF (reader GEOTIFF_2)
    -> Reprojector_4
    -> Clipper_2 [CANDIDATE]
Reprojector_4 [off]
    DEST = EPSG:25833
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Clipper_2 [CANDIDATE]
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterMosaicker_2
RasterMosaicker_2
    ACCUM_ATTRS_NAME = Use Attributes From One Feature
    INTERPOLATION_TYPE = NearestNeighbor
    MERGE_PALETTES_NAME = Yes
    NODATA_OVERWRITE = No
    OVERLAPPING_VALUES = last
    SNAPPING_TYPE = RESAMPLE
    INTERPOLATION_TYPE_NAME = Nearest Neighbor
    MERGE_PALETTES = Yes
    SNAPPING_TYPE_NAME = Resample
    -> RasterToPolygonCoercer_2
RasterToPolygonCoercer_2
    EXTRACT_NODATA = No
    LABEL_ATTRIBUTE = _label
    PRESERVE_ATTRIBUTES_LOOKUP = YES
    EXTRACT_NODATA_LOOKUP = No
    PRESERVE_ATTRIBUTES = Yes
    POLYGONS -> Shapefile3 (writer SHAPEFILE_3)
Shapefile3 (writer SHAPEFILE_3)
    attributes: Q__clipped varchar(3), Q__label varchar(254)
GEOTIFF (reader GEOTIFF_3)
    -> Reprojector_3
    -> Clipper_3 [CANDIDATE]
Reprojector_3 [off]
    DEST = EPSG:25833
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Clipper_3 [CANDIDATE]
Clipper_3
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterMosaicker_3
RasterMosaicker_3
    ACCUM_ATTRS_NAME = Use Attributes From One Feature
    INTERPOLATION_TYPE = NearestNeighbor
    MERGE_PALETTES_NAME = Yes
    NODATA_OVERWRITE = No
    OVERLAPPING_VALUES = last
    SNAPPING_TYPE = RESAMPLE
    INTERPOLATION_TYPE_NAME = Nearest Neighbor
    MERGE_PALETTES = Yes
    SNAPPING_TYPE_NAME = Resample
    -> RasterToPolygonCoercer_3
RasterToPolygonCoercer_3
    EXTRACT_NODATA = No
    LABEL_ATTRIBUTE = _label
    PRESERVE_ATTRIBUTES_LOOKUP = YES
    EXTRACT_NODATA_LOOKUP = No
    PRESERVE_ATTRIBUTES = Yes
    POLYGONS -> Shapefile4 (writer SHAPEFILE_4)
Shapefile4 (writer SHAPEFILE_4)
    attributes: Q__clipped varchar(3), Q__label varchar(254)
GEOTIFF (reader GEOTIFF_4)
    -> Reprojector_5
    -> Clipper_4 [CANDIDATE]
Reprojector_5 [off]
    DEST = EPSG:25833
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Clipper_4 [CANDIDATE]
Clipper_4
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterMosaicker_4
RasterMosaicker_4
    ACCUM_ATTRS_NAME = Use Attributes From One Feature
    INTERPOLATION_TYPE = NearestNeighbor
    MERGE_PALETTES_NAME = Yes
    NODATA_OVERWRITE = No
    OVERLAPPING_VALUES = last
    SNAPPING_TYPE = RESAMPLE
    INTERPOLATION_TYPE_NAME = Nearest Neighbor
    MERGE_PALETTES = Yes
    SNAPPING_TYPE_NAME = Resample
    -> RasterToPolygonCoercer_4
RasterToPolygonCoercer_4
    EXTRACT_NODATA = No
    LABEL_ATTRIBUTE = _label
    PRESERVE_ATTRIBUTES_LOOKUP = YES
    EXTRACT_NODATA_LOOKUP = No
    PRESERVE_ATTRIBUTES = Yes
    POLYGONS -> Shapefile5 (writer SHAPEFILE_5)
Shapefile5 (writer SHAPEFILE_5)
    attributes: Q__clipped varchar(3), Q__label varchar(254)
GEOTIFF (reader GEOTIFF_5)
    -> Reprojector_6
    -> Clipper_5 [CANDIDATE]
Reprojector_6 [off]
    DEST = EPSG:25833
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Clipper_5 [CANDIDATE]
Clipper_5
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterMosaicker_5
RasterMosaicker_5
    ACCUM_ATTRS_NAME = Use Attributes From One Feature
    INTERPOLATION_TYPE = NearestNeighbor
    MERGE_PALETTES_NAME = Yes
    NODATA_OVERWRITE = No
    OVERLAPPING_VALUES = last
    SNAPPING_TYPE = RESAMPLE
    INTERPOLATION_TYPE_NAME = Nearest Neighbor
    MERGE_PALETTES = Yes
    SNAPPING_TYPE_NAME = Resample
    -> RasterToPolygonCoercer_5
RasterToPolygonCoercer_5
    EXTRACT_NODATA = No
    LABEL_ATTRIBUTE = _label
    PRESERVE_ATTRIBUTES_LOOKUP = YES
    EXTRACT_NODATA_LOOKUP = No
    PRESERVE_ATTRIBUTES = Yes
    POLYGONS -> Shapefile6 (writer SHAPEFILE_6)
Shapefile6 (writer SHAPEFILE_6)
    attributes: Q__clipped varchar(3), Q__label varchar(254)
GEOTIFF (reader GEOTIFF_6)
    -> Reprojector_7
    -> Clipper_6 [CANDIDATE]
Reprojector_7 [off]
    DEST = EPSG:25833
    INTERPOLATION_TYPE = ,NearestNeighbor
    RASTER_CELL_SIZE_LOOKUP = ,PreserveCells
    RASTER_TOLERANCE = 0.0
    INTERPOLATION_TYPE_NAME = Nearest Neighbor
    RASTER_CELL_SIZE = Preserve Cells
    REPROJECTED -> Clipper_6 [CANDIDATE]
Clipper_6
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> RasterMosaicker_6
RasterMosaicker_6
    ACCUM_ATTRS_NAME = Use Attributes From One Feature
    INTERPOLATION_TYPE = NearestNeighbor
    MERGE_PALETTES_NAME = Yes
    NODATA_OVERWRITE = No
    OVERLAPPING_VALUES = last
    SNAPPING_TYPE = RESAMPLE
    INTERPOLATION_TYPE_NAME = Nearest Neighbor
    MERGE_PALETTES = Yes
    SNAPPING_TYPE_NAME = Resample
    -> RasterToPolygonCoercer_6
RasterToPolygonCoercer_6
    EXTRACT_NODATA = No
    LABEL_ATTRIBUTE = _label
    PRESERVE_ATTRIBUTES_LOOKUP = YES
    EXTRACT_NODATA_LOOKUP = No
    PRESERVE_ATTRIBUTES = Yes
    POLYGONS -> Shapefile7 (writer SHAPEFILE_7)
Shapefile7 (writer SHAPEFILE_7)
    attributes: Q__clipped varchar(3), Q__label varchar(254)
