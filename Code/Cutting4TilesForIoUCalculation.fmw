FME workspace Cutting4TilesForIoUCalculation.fmw

Parameters:
- SourceDataset_SHAPEFILE = G:\Berlin_Potsdam_2023\09_TrueOrthophotoTileOverview_SHP\TrueOrthophotoTileOverview.shp   # Source Esri Shapefile(s)
- FEATURE_TYPES =
- DestDataset_SHAPEFILE_2 = F:\KRE\SolaranlagenBerlin\results\6 IoU_calculation\cleaned_clippedBuildings_o1\915272.shp   # Destination Esri Shapefile Folder
- DestDataset_SHAPEFILE_8 = F:\KRE\SolaranlagenBerlin\results\6 IoU_calculation\cleaned_clippedBuildings_o1\005101.shp   # Destination Esri Shapefile Folder
- DestDataset_SHAPEFILE_7 = F:\KRE\SolaranlagenBerlin\results\6 IoU_calculation\cleaned_clippedBuildings_o1\005119.shp   # Destination Esri Shapefile Folder
- DestDataset_SHAPEFILE = F:\KRE\SolaranlagenBerlin\results\6 IoU_calculation\cleaned_clippedBuildings_o1\924047.shp   # Destination Esri Shapefile Folder
- SourceDataset_SHAPEFILE_3 = F:\KRE\SolaranlagenBerlin\results\5 Analyse_cleaned_clippedBuildings\BerlinSolarSystems_25833_clean_clippedBuilding2_area_o1.shp\o1.shp   # Source Esri Shapefile(s)

Readers:
- SHAPEFILE_1: SHAPEFILE from $(SourceDataset_SHAPEFILE)
- SHAPEFILE_2: SHAPEFILE from $(SourceDataset_SHAPEFILE_3)

Writers:
- SHAPEFILE_3: SHAPEFILE to $(DestDataset_SHAPEFILE) in EPSG:25833
- SHAPEFILE_4: SHAPEFILE to $(DestDataset_SHAPEFILE_2) in EPSG:25833
- SHAPEFILE_5: SHAPEFILE to $(DestDataset_SHAPEFILE_8) in EPSG:25833
- SHAPEFILE_6: SHAPEFILE to $(DestDataset_SHAPEFILE_7) in EPSG:25833

o1 (reader SHAPEFILE_2)
    attributes: Q__uuid varchar(36), Q__clipped varchar(3), Nutzung varchar(254), PLZ varchar(254), Adresse varchar(254), Q__area number(31,15)
    -> Clipper [CANDIDATE]
    -> Clipper_2 [CANDIDATE]
    -> Clipper_3 [CANDIDATE]
    -> Clipper_4 [CANDIDATE]
TrueOrthophotoTileOverview (reader SHAPEFILE_1)
    attributes: TILENAME varchar(10), X_MIN number(15,0), Y_MIN number(15,0), X_MAX number(15,0), Y_MAX number(15,0)
    -> 924047
    -> 915272
    -> 005101
    -> 005119
924047: Tester
    BOOL_OP = OR
    TEST_CLAUSE = TEST @Value(TILENAME) = 924047
    TEST_MODE = TEST
    PASSED -> Clipper [CLIPPER]
Clipper
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> 924047 (writer SHAPEFILE_3)
924047 (writer SHAPEFILE_3)
    attributes: Q__uuid varchar(36), Q__clipped varchar(3), Nutzung varchar(254), PLZ varchar(254), Adresse varchar(254), Q__area number(31,15), Q__clipp00 varchar(3)
915272: Tester
    BOOL_OP = OR
    TEST_CLAUSE = TEST @Value(TILENAME) = 915272
    TEST_MODE = TEST
    PASSED -> Clipper_2 [CLIPPER]
Clipper_2
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> 915272 (writer SHAPEFILE_4)
915272 (writer SHAPEFILE_4)
    attributes: Q__uuid varchar(36), Q__clipped varchar(3), Nutzung varchar(254), PLZ varchar(254), Adresse varchar(254), Q__area number(31,15), Q__clipp00 varchar(3)
005101: Tester
    BOOL_OP = OR
    TEST_CLAUSE = TEST @Value(TILENAME) = 005101
    TEST_MODE = TEST
    PASSED -> Clipper_3 [CLIPPER]
Clipper_3
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> 005101 (writer SHAPEFILE_5)
005101 (writer SHAPEFILE_5)
    attributes: Q__uuid varchar(36), Q__clipped varchar(3), Nutzung varchar(254), PLZ varchar(254), Adresse varchar(254), Q__area number(31,15), Q__clipp00 varchar(3)
005119: Tester
    BOOL_OP = OR
    TEST_CLAUSE = TEST @Value(TILENAME) = 005119
    TEST_MODE = TEST
    PASSED -> Clipper_4 [CLIPPER]
Clipper_4
    ADD_NODATA = YES
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> 005119 (writer SHAPEFILE_6)
005119 (writer SHAPEFILE_6)
    attributes: Q__uuid varchar(36), Q__clipped varchar(3), Nutzung varchar(254), PLZ varchar(254), Adresse varchar(254), Q__area number(31,15), Q__clipp00 varchar(3)
