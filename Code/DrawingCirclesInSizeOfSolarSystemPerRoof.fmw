FME workspace DrawingCirclesInSizeOfSolarSystemPerRoof.fmw

Parameters:
- SourceDataset_SHAPEFILE = F:\KRE\SolaranlagenBerlin\results\AllBerlinSolarSystems_25833_clean_clippedBuilding2.shp\clippedBuilding2.shp   # Source Esri Shapefile(s)
- SourceDataset_SHAPEFILE_3 = C:\Users\hkretz\OneDrive - virtualcitysystems GmbH\2 interdisziplinäresProjekt\6 Auswertung\Gebäudeverschnitt\gebäudeBerlin.shp\gebäudeBerlin.shp   # Source Esri Shapefile(s)
- DestDataset_SHAPEFILE = F:\KRE\SolaranlagenBerlin\results\7 MSDR_mergedPolygones_perBuilding\solarCircles_filteredBig.shp   # Destination Esri Shapefile Folder

Readers:
- SHAPEFILE_1: SHAPEFILE from $(SourceDataset_SHAPEFILE)
- SHAPEFILE_2: SHAPEFILE from $(SourceDataset_SHAPEFILE_3)

Writers:
- SHAPEFILE_3: SHAPEFILE to $(DestDataset_SHAPEFILE) in EPSG:25833

gebäudeBerlin (reader SHAPEFILE_2)
    attributes: uuid varchar(254), gfk long, bezgfk varchar(254), ofl long, bezofl varchar(254), aog long, aug long, hoh varchar(254), bat long, bezbat varchar(254), nam varchar(254), baw long, bezbaw varchar(254), zus long, bezzus varchar(254), gkn varchar(254), des varchar(254), bezdes varchar(254), lag varchar(254), namlag varchar(254), hnr varchar(254), pnr varchar(254), lnr varchar(254), bezeich varchar(254)
    -> SpatialFilter [Filter]
    -> SpatialFilter_2 [Candidate]
clippedBuilding2 (reader SHAPEFILE_1)
    attributes: Q__uuid varchar(36), Q__clipped varchar(3), Nutzung varchar(254), PLZ varchar(254), Adresse varchar(254)
    -> SpatialFilter [Candidate]
    -> SpatialFilter_2 [Filter]
SpatialFilter_2
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> CenterPointReplacer
CenterPointReplacer
    POINTTYPE = CENTEROFGRAV
    POINT -> FeatureMerger [REQUESTOR]
SpatialFilter
    AGGREGATE_HANDLING = Yes
    ATTR_ACCUM_MODE = Merge Filter
    ATTR_CONFLICT_RES = Use Candidate
    BASE_TYPE = Multiple Filters
    CURVE_BOUNDARY_RULE_PARAM = Default Rule
    PASS_CRITERIA = Pass Against One Filter
    PREDATTR = _predicate
    PREDICATES = INTERSECTS
    USE_BOUNDING_BOX = No
    PASSED -> AreaCalculator
AreaCalculator
    AREA_ATTR = _area
    AREA_TYPE = Plane Area
    MULT = 1
    -> StatisticsCalculator
StatisticsCalculator
    ATTR_ACCUM_MODE = None
    CALCULATION_MODE = NUMERIC
    FEAT_STATS = _area,NUMERIC_MODE,,,,SUM,,,,,,,,,
    GROUP_BY = Adresse
    COMPLETE -> Tester
Tester
    BOOL_OP = OR
    TEST_CLAUSE = TEST @Value(_area.sum) < 7953
    TEST_MODE = TEST
    PASSED -> FeatureMerger [SUPPLIER]
FeatureMerger
    ATTR_ACCUM_MODE = Merge Supplier
    ATTR_CONFLICT_RES_LOOKUP = REQUESTOR_IF_CONFLICT
    IGNORE_NULLS = No
    JOIN_KEYS = @Value(namlag) @Value(Adresse) AUTO
    MERGE_TYPE = Attributes Only
    PROCESS_DUPS = NO
    REJECT_NULL_MISSING_KEYS = No
    SUPPLIERS_FIRST = No
    ATTR_CONFLICT_RES = Use Requestor
    MERGED -> AttributeCreator
AttributeCreator
    ATTR_TABLE = SET_TO radius (varchar(200)) = @sqrt(@Value(_area.sum) / @pi())
    -> Bufferer
    -> AttributeCreator_Output
Bufferer
    ANGLE = 22.5
    CAP_STYLE_LOOKUP = CAP_ROUND
    CORNER_STYLE_LOOKUP = JOIN_ROUND
    MODE = AREA
    OFFSET = @Value(radius)
    OFFSET_UNITS = NONE
    PRECISION = EXACT
    CAP_STYLE = Round
    CORNER_STYLE = Round
    BUFFERED -> GeometryValidator
GeometryValidator
    ISSUE_ATTR_NAME = _issues
    PRESETS = Custom
    REPAIR = Yes
    RULES = MISMATCHED_DIMENSIONS FORCE_DIMENSION]2D]MISMATCHED_Z_VAL]<Unused>]FME_CONTROLLER_QUERY_FILE]transformers/dependencies/geometryvalidator8/MISMATCHED_DIMENSIONS.fme]FME_CONTROLLER_CHOICE]MISMATCHED_DIMENSIONS NAN_REMOVAL PROCESS_MEASURE]NO]FME_CONTROLLER_QUERY_FILE]transformers/dependencies/geometryvalidator8/NAN_REMOVAL.fme]FME_CONTROLLER_CHOICE]NAN_REMOVAL NULL_REMOVAL FME_CONTROLLER_QUERY_FILE]transformers/dependencies/geometryvalidator8/NULL_REMOVAL.fme]FME_CONTROLLER_CHOICE]NULL_REMOVAL SELF_INTERSECTING CHECK_HOLE_TOUCHING_POLYGON]No]CONNECT_Z_MODE_SI]FIRST_WINS]SELF_INTERSECTION_TOLERANCE]Automatic]INTERSECT_ACROSS_MULTIS]No]FME_CONTROLLER_QUERY_FILE]transformers/dependencies/geometryvalidator8/SELF_INTERSECTING.fme]FME_CONTROLLER_CHOICE]SELF_INTERSECTING
    SUMMARY = Detailed
    PASSED -> SolarCircles (writer SHAPEFILE_3)
SolarCircles (writer SHAPEFILE_3)
    attributes: radius varchar(200), Q__uuid varchar(36), Nutzung varchar(254), PLZ varchar(254), Adresse varchar(254), Q__area double, Q__area_su double
AttributeCreator_Output: Inspector [off]
